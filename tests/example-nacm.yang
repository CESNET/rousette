module example-nacm {
  yang-version 1.1;
  prefix aha;
  namespace "http://example.com";

  import ietf-netconf-acm {
    prefix nacm;
    reference
      "RFC 8341: Network Configuration Access Control Model";
  }

  leaf denyAllLeaf {
    nacm:default-deny-all;
    type string;
  }

  leaf allowAllLeaf {
    type string;
  }
}
