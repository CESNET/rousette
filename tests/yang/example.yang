module example {
  yang-version 1.1;
  namespace "http://example.tld/example";
  prefix ex;

  feature f1 { }
  feature f2 { }

  identity base-identity {
  }

  identity derived-identity {
    base base-identity;
  }

  identity fruit { }
  identity apple {
    base fruit;
  }

  leaf top-level-leaf { type string; }
  leaf top-level-leaf2 { type string; default "x"; }

  list top-level-list {
    key "name";
    leaf name { type string; }
  }
  leaf-list top-level-leaf-list { type int32; }

  container channel-plan {
    list channel {
      key "name";
      leaf name { type string; }
      leaf lower-frequency {
        type int32;
        units "Hz";
      }
      leaf upper-frequency {
        type int32;
        units "Hz";
      }

      must "lower-frequency < upper-frequency" {
        description "The lower frequency must be less than the upper frequency.";
      }
    }
  }

  container tlc {
    if-feature f1;
    list list {
      key "name";
      leaf name { type string; }
      leaf-list collection { type int32; }
      list nested {
        key "first second third";
        leaf first { type string; }
        leaf second { type int32; }
        leaf third { type string; }
        leaf fourth { type string; }
        container data {
          leaf a { type string; }
          container other-data {
            leaf b { type string; }
            leaf c { type string; }
          }
        }
      }
      choice choose {
        mandatory true;
        leaf choice1 { type string; }
        leaf choice2 { type string; }
      }
      action example-action {
        input {
          leaf i { type string; }
        }
        output {
          leaf o { type string; }
        }
      }
      notification notif {
        leaf message {
          type string;
        }
      }
    }
    list key-less-list {
      config false;
      leaf name { type string; }
    }
    leaf-list decimal-list {
        type decimal64 {
            fraction-digits 2;
        }
    }
    leaf status {
      type enumeration {
        enum on { }
        enum off { }
      }
    }
  }

  container f {
    if-feature f2;
    leaf hello { type string; }
  }

  container a {
    container b {
      container c {
        leaf enabled {
          type boolean;
          default true;
        }
        leaf blower {
          type string;
        }
      }
    }
    container b1 { }
    leaf something { type string; }
  }

  container two-leafs {
    leaf a { type string; }
    leaf b { type string; }
  }

  container config-nonconfig {
    leaf config-node {
      config true;
      type string;
    }
    leaf nonconfig-node {
      config false;
      type string;
    }
  }

  container ordered-lists {
    list lst {
      ordered-by user;
      key "name";
      leaf name { type string; }
    }
    leaf-list ll {
      ordered-by user;
      type string;
    }
    leaf-list ll2 {
      ordered-by user;
      type string;
    }
  }

  list list-with-union-keys {
    key "type name";
    leaf type {
      type union {
        type identityref {
          base base-identity;
        }
        type enumeration {
          enum zero;
          enum one;
        }
        type leafref {
          require-instance true;
          path "/fruit-list";
        }
        type string;
      }
    }
    leaf name { type string; }
    leaf text { type string; }
  }

  leaf-list leaf-list-with-identity-key {
    type identityref { base base-identity; }
  }

  leaf-list fruit-list {
    type identityref { base fruit; }
  }

  rpc test-rpc {
    input {
      leaf i {
        type string;
        mandatory true;
      }
    }
    output {
      leaf out1 { type string; }
      leaf out2 { type string; }
    }
  }

  rpc test-rpc-no-output {
    input {
      leaf number { type int32; }
      leaf string { type string; }
    }
  }

  rpc test-rpc-no-input {
    output {
      leaf out1 { type string; }
      leaf out2 { type string; }
    }
  }

  rpc test-rpc-no-input-no-output {

  }

  notification eventA {
    leaf message {
      type string;
    }

    leaf progress {
      type int8 {
        range "0 .. 100";
      }
    }
  }

  notification eventB { }
}
