module example-delete {
  yang-version 1.1;
  namespace "http://example.tld/example-delete";
  prefix exdel;

  list secret {
    key "name";
    leaf name {
      type string;
    }
  }

  list immutable {
    key "name";
    leaf name {
      type string;
    }
  }
}
