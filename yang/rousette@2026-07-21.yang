module rousette {
  namespace "urn:cesnet:params:xml:ns:yang:czechlight:rousette";
  prefix rousette;

  import ietf-restconf {
    prefix rc;
  }

  revision 2026-07-21 {
    description "Refactored to use rc:yang-data.";
  }

  revision 2026-04-20 {
    description "Initial version.";
  }

  rc:yang-data "uri-error" {
    container uri-error {
      description "Structured error information for URI syntax errors, for use in RESTCONF error-info.";
      leaf offset {
        type uint32;
        description "Byte offset in the URI where the syntax error was detected.";
      }
      leaf expected-token {
        type string;
        description "The token expected at the error position.";
      }
    }
  }
}
